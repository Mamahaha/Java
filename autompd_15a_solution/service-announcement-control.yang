module service-announcement-control {
  namespace "http://com.ericsson/ns/bvps/service-announcement-control";
  
  prefix "sac";

  import ietf-inet-types {
    prefix inet;
  }

  import tailf-ncs {
    prefix ncs;
  }

  import tailf-common {
    prefix tailf;
  }

  import service-announcement {
    prefix sa;
  }

  augment /ncs:services/ncs:properties {
    
    container access-points {
      list access-point {
        key "access-point-name";

        description "";

        leaf access-point-name {
          type inet:uri;
        }
      }
    }

    container alternative-unicast-delivery-uris {
      list alternative-unicast-delivery {
        key "alternative-unicast-delivery-uri";

        leaf alternative-unicast-delivery-uri {
          type inet:uri;
        }

        leaf description {
          description "Description of the alternative unicast URI";
          type string;
        }
      }
    }

    container settings {

      leaf base-url {
        type inet:uri;
      }
      tailf:validate base-url {
	tailf:dependency "base-url";
      }
      
      leaf base-urn {
        type sa:urn-t;
        tailf:info "Example: urn:xyz:b23";
      }
      
      container cdn {
	container sftp-config {
	  leaf host {
	    type string;
	  }
	  
	  leaf port {
	    type uint16;
	    default 22;
	  }
	  
	  leaf username {
	    type string;
	  }
	  
	  leaf password {
	    type string;
	  }
	}

    container sftp-config2 {
	  leaf host {
	    type string;
	  }
	  
	  leaf port {
	    type uint16;
	    default 22;
	  }
	  
	  leaf username {
	    type string;
	  }
	  
	  leaf password {
	    type string;
	  }
	}
	
	leaf poll-interval {
	  description "Time (in minutes) to wait between attempts at retrieving files.";
	  type uint32;
	  default 15;
	}

    leaf mpd-poll-interval {
      description "Time (in seconds) to wait between attempts at retrieving MPD files from CDN/DMF.";
      type uint32;
      default 5;
    }
    
	leaf saf-path {
	  description "A location to which BVPS will write the service announcement file.";
	  type inet:uri;
	}

	leaf msdc-path {
	  tailf:hidden embm;
	  type inet:uri;
	}

	leaf msdc-file-name {
	  tailf:hidden embm;
	  type inet:uri;
	}

	leaf boot-strap-path {
	  type inet:uri;
	}

	leaf boot-strap-file-name {
	  type inet:uri;
	}

	leaf mmwc-path {
	  type inet:uri;
	}

	leaf mmwc-file-name {
	  type inet:uri;
	}
    
	leaf boot-config-path {
	  type inet:uri;
	}

	leaf boot-config-file-name {
	  type inet:uri;
	}

	leaf combination {
	  description "Specify whether BMC should combine Bootstrap file and MMW configuration file 
	  			   into one Multipart MIME file which is then compressed as GZip.";
	  default false;
	  type boolean;
	}

	leaf saf-upload-interval {
	  description "Minimum time in seconds between SAF uploads to the CDN.";
	  type uint16;
	  default 300;
	}
      }
      
      leaf msdc-service {
	description "Points out the service containing the FLUTE session
                     to be used for the delivery of the MSDC file.";
    
	tailf:hidden embm;
	type leafref {
	  path "/ncs:services/ncs:service/ncs:object-id";
        }
      }
      
      leaf valid-until-timer {
	type uint32;
	description 
	  "Value for increment of valid until timer. Value in minutes.
           Default value 2880 minutes = 48 hours.
	   Valid Until Frequency must always be less than Valid Until Timer";
	default 2880;
      }
      leaf valid-until-frequency {
	type uint32 {
	  range "1..max";
	}
	description 
	  "Value for update frequency of valid until timer. Value in minutes.
           Default value 1440 minutes = 24 hours.
	   Valid Until Frequency must always be less than Valid Until Timer";
	default 1440;
      }
      must "valid-until-frequency<valid-until-timer" {
	error-message "valid-until-frequency must be less than valid-until-timer";
	tailf:dependency "valid-until-timer";
	tailf:dependency "valid-until-frequency";
      } 
      leaf initial-valid-until-frequency {
	type uint32;
	description 
	  "Value for when the first update of valid until timer shall be done after system start.
           Value in minutes.
           Default value 5 minutes";
	default 5;
      }
      container device-connection {
        leaf virtual-traffic-address {
          type string;
          default "127.0.0.1";
          description "The virtual traffic IP address of BMC in HA solution.
                    This address is used as local bind address by BMC to communicate with BDC devices,
                    other local address of BMC will be rejected by the iptables of BDC devices in HA solution.";
        }
        leaf virtual-management-address {
          type string;
          default "127.0.0.1";
          description "The virtual management IP address of BMC in HA solution.
                    This address is used as local bind address by BMC to communicate with NCM devices or Reporting server,
                    other local address of BMC will be rejected by the iptables of NCM devices or Reporting server in HA solution.";
        }
      }
    }
  }
}
